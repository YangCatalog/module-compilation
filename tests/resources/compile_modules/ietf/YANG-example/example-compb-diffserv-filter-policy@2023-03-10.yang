module example-compb-diffserv-filter-policy {
  yang-version 1.1;
  namespace "urn:ietf:params:xml:ns:yang:" +
            "example-compb-diffserv-filter-policy";
  prefix compb-filter-policy;

  import iana-qos-types {
    prefix qos-types;
    reference
      "RFC XXXX: YANG Models for Quality of Service (QoS).";
  }
  import ietf-traffic-policy {
    prefix policy;
  }
  import ietf-qos-action {
    prefix action;
  }
  import ietf-diffserv {
    prefix diffserv;
  }

  organization
    "Company B";

  contact
    "Editor:   XYZ
               <mailto:xyz@compb.com>";

  description
    "This module contains a collection of YANG definitions for
     configuring diffserv specification implementations.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2023-03-10 {
    description
      "Initial revision of diffserv policy";
    reference
      "RFC XXXX: YANG Data Model for QoS.";
  }

  /*
   * The policy must be of either type v4 or v6. Corresponding
   * address types must be used. Enforce with "must" statement?
   */
  identity v4-diffserv-policy-type {
    base qos-types:policy-type;
    description
      "This defines default policy-type";
  }

  identity v6-diffserv-policy-type {
    base qos-types:policy-type;
    description
      "This defines default policy-type";
  }

  /*************************************************
   * Classification types
   *************************************************/

  identity forwarding-class {
      base qos-types:filter-type;
      description
        "Forwarding class filter type";
  }

  identity internal-loss-priority  {
     base qos-types:filter-type;
     description
        "Internal loss priority filter type";
  }

  grouping drop {
    container drop {
      leaf drop {
        type empty;
        description
          "drop action";
      }
      description
        "drop container";
    }
    description
      "drop grouping";
  }

  grouping forwarding-class {
    list forwarding-class {
      key "forwarding-class";
      description
        "list of forwarding-classes";
      leaf forwarding-class {
        type string;
        description
          "Forwarding class name";
      }
    }
    description
      "Filter containing list of forwarding classes";
  }
  grouping loss-priority {
    list loss-priority {
      key "loss-priority";
      description
        "list of loss-priorities";
      leaf loss-priority {
        type enumeration {
          enum high {
           description "High Loss Priority";
          }
          enum medium-high {
           description "Medium-high Loss Priority";
          }
          enum medium-low {
           description "Medium-low Loss Priority";
          }
          enum low {
           description "Low Loss Priority";
          }
        }
        description
          "Loss-priority";
      }
    }
    description
      "Filter containing list of loss priorities";
  }

  augment "/policy:policies" +
          "/policy:policy" +
          "/policy:classifier" +
          "/policy:inline/policy:filter" +
          "/diffserv:filter-params" {
    case forwarding-class {
        uses forwarding-class;
      description
        "Filter Type Internal-loss-priority";
    }
    case internal-loss-priority {
        uses loss-priority;
      description
        "Filter Type Internal-loss-priority";
    }
    description
      "Augments Diffserv Classifier with vendor" +
      " specific types";
  }

  /*************************************************
   * Actions
   *************************************************/

  identity mark-fwd-class {
    base qos-types:action-type;
    description
      "mark forwarding class action type";
  }

  identity mark-loss-priority {
    base qos-types:action-type;
    description
      "mark loss-priority action type";
  }

  grouping mark-fwd-class {
    container mark-fwd-class {
      leaf forwarding-class {
        type string;
        description
          "Forwarding class name";
      }
      description
        "mark-fwd-class container";
    }
    description
      "mark-fwd-class grouping";
  }

  grouping mark-loss-priority {
    container mark-loss-priority {
      leaf loss-priority {
        type enumeration {
          enum high {
           description "High Loss Priority";
          }
          enum medium-high {
           description "Medium-high Loss Priority";
          }
          enum medium-low {
           description "Medium-low Loss Priority";
          }
          enum low {
           description "Low Loss Priority";
          }
        }
        description
          "Loss-priority";
      }
      description
        "mark-loss-priority container";
    }
    description
      "mark-loss-priority grouping";
  }

  augment "/policy:policies" +
          "/policy:policy" +
          "/policy:classifier" +
          "/policy:action" +
          "/policy:action-params" {
    case mark-fwd-class {
      uses mark-fwd-class;
      description
        "Mark forwarding class in the packet";
    }
    case mark-loss-priority {
        uses mark-loss-priority;
      description
        "Mark loss priority in the packet";
    }
    case meter-reference {
        uses action:meter-reference;
      description
        "Assign a meter as an action";
    }
    case discard {
        uses action:discard;
      description
        "Discard action";
    }
    case count {
        uses action:count;
      description
        "Count action - explicit count configuration";
    }
    description
      "Augments common diffserv policy actions";
  }

  augment "/action:meters" +
          "/action:meter" +
          "/action:meter-types" +
          "/action:single-rate-three-color-meter-type" +
          "/action:single-rate-three-color-meter" {
     leaf one-rate-color-aware {
      type boolean;
      description
        "This defines if the meter is color-aware";
    }
    description
      "Augmentation of color-aware flag";
  }
  augment "/action:meters" +
          "/action:meter" +
          "/action:meter-types" +
          "/action:two-rate-three-color-meter-type" +
          "/action:two-rate-three-color-meter" {
     leaf two-rate-color-aware {
      type boolean;
      description
        "This defines if the meter is color-aware";
    }
    description
      "Augmentation of color-aware flag";
  }

  /* example of augmenting a meter template with a
  /* vendor specific action */
  augment "/action:meters" +
          "/action:meter" +
          "/action:meter-types" +
          "/action:single-rate-two-color-meter-type" +
          "/action:single-rate-two-color-meter" +
          "/action:exceed-action" +
          "/action:action" +
          "/action:action-val" {
    case meter-action-drop {
      description
          "meter drop";
           uses drop;
    }

    description
      "Augment the actions to basic meter";
  }

}
