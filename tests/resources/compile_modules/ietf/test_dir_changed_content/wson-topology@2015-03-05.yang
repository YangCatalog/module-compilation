module   wson-topology {
   namespace "urn:ietf:params:xml:ns:yang:wson-topology";

   prefix wson;

   import ietf-inet-types {
      prefix inet;
   }

   organization
        "IETF CCAMP Working Group";

   contact
        "Editor:   Young Lee  <leeyoung@huawei.com>";

   description
        "This module contains a collection of YANG definitions for
        RWA WSON.

        Copyright (c) 2015 IETF Trust and the persons identified as
        authors of the code.  All rights reserved.

        Redistribution and use in source and binary forms, with or
        without modification, is permitted pursuant to, and subject
        to the license terms contained in, the Simplified BSD
        License set forth in Section 4.c of the IETF Trust's Legal
        Provisions Relating to IETF Documents
        (http://trustee.ietf.org/license-info).";

   revision 2015-03-05 {
        description
            "Initial revision.";
        reference
            "RFC XXX: A Yang Data Model for WSON Optical Networks ";
   }

   typedef wson-topology-id {
      type inet:uri;
      description
         "The WSON Topology ID";

   }

   typedef wson-node-id {
      type inet:ip-address;
      description
         "The WSON Node ID";
   }

   typedef wson-node-id {
      type inet:ip-address;
      description
         "The WSON Node ID TEST";
   }

   typedef devicetype {
      type enumeration {
         enum adm {
            value 1;

            description
               "Device is ADM";
         }
         enum roadm {
            value 2;
         description
               "Device is ROAMD/OXC";
         }
      }
      description
         "device type: fixed (ADM) or switched (ROADM/OXC)";
   }

   typedef directionality {
      type enumeration {
         enum bidir {
            value 0;
            description
               "bi-directional";
         }
         enum input {
            value 1;

            description
               "input direction";
         }
         enum output {
            value 2;
            description
               "output direction";
         }
      }
      description
         "The directionality of link set";
   }

   typedef linkset-format {
      type enumeration {
         enum link-local-identifier{
            value 1;
            description
               "";
         }
         enum local-interface-ipv4{
            value 2;
            description
               "";
         }
         enum local-interface-ipv6{
            value 3;
            description
               "";
         }
      }
      description
         "linkset type; link local/ipv4/ipv6";
   }

   typedef wson-interface-ref {
      type leafref {
         path "/wson-topology/wson-topology/wson-node/" +
              "wson-interface/wson-interface-id";
      }
      description
      "This type is used by data models that need to
      reference WSON interface.";
   }

   container wson-topology {
      description
         "TBD";
      list wson-topology {
         key "wson-topology-id";
         description
            "The WSON Topology";
         leaf wson-topology-id {
            type wson-topology-id;
            description
               "The WSON Topology Identifier";
         }
         leaf name {
            type string;
            description
               "TBD";
         }

         list wson-node {
            key "wson-node-id";
            description
               "The WSON node";
            leaf wson-node-id {
               type wson-node-id;
               description
                  "The WSON Node ID";
            }

            list wson-interface {
               key "wson-interface-id";
               description
                  "The list of WSON Interface";
               leaf wson-interface-id {
                  type linkset-format;
                  description
                     "TBD";
               }
            }

            leaf-list wavelength-available-bitmap {
               type boolean;
               description
                  "array of bits (i.e., bitmap) that indicates
                  if a wavelength is available or not on the
                  interface.";
            }

            list connectivity-matrix {
               key "matrix-id";
               description
                  "connectivity-matrix of WSON node";
               reference
                  "based on draft-ietf-ccamp-general-constraint-
encode";
               leaf matrix-id {
                  type uint8;
                  description
                     "matrix identifier";
               }

               leaf device-type {
               type devicetype;
               description
                     "device type: fixed (ADM) or switched
                     (ROADM/OXC)";
               }
               leaf dir {
                  type directionality;
                  description
                     "bi-directionality or input or output
                     of link set";
               }
               leaf format {
                  type linkset-format;
                  description
                     "format of identifier";
               }
               list matrix-interface {
                  key "in-port-id";

                  description
                     "matrix-interface describes input-ports
                     and out-ports around a connectivity
                     matrix";

                  leaf in-port-id {
                     type wson-interface-ref;
                     description
                        "The reference to in-port";
                  }

                  leaf out-port-id {
                     type wson-interface-ref;
                     description
                        "The reference to out-port";
                  }
               }
            }
            list resource-pool {
               key "resource-pool-id";
               description
                  "The resource pool list";

               leaf resource-pool-id {
                  type uint32;
                  description
                     "The resource pool ID";
               }
               leaf pool-state {
                  type boolean;
                  description
                     "TRUE is state UP; FALSE is state down";
               }
               list matrix-interface {
                  key "in-port-id";
                  description
                     "pool is described as matrix-interface
                     with input-ports and output-ports
                     around the pool";
                  leaf in-port-id {
                     type wson-interface-ref;
                     description
                        "The reference to in-interface";

                  }
                  leaf out-port-id {
                     type wson-interface-ref;
                     description
                        "The reference to out-interface";
                  }
               }
            }
         }
      }
   }
}
